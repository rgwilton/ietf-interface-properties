module iana-if-property-type {
  namespace "urn:ietf:params:xml:ns:yang:iana-if-property-type";
  prefix ianaifp;

  organization "IANA";
  contact "";
  description
    "This YANG module defines YANG identities for IANA-registered
     interface property types.

     This YANG module is maintained by IANA.

     The latest revision of this YANG module can be obtained from
     the IANA web site.

     Requests for new values should be made to IANA via
     email (iana&iana.org).

     Copyright (c) 2017 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     The initial version of this YANG module is part of XXX;
     see the RFC itself for full legal notices.";
  reference
    "IANA 'interface property definitions' registry.";

  revision 2017-06-27 {
    description
      "Initial revision";
    reference
      "RFC XXX: IANA Interface Property Type YANG Module";
  }

  identity iana-if-property-type {
    description
      "Base identity from which specific interface property types are
       derived.";
  }

  identity physical {
    base iana-if-property-type;
    description
      "This property represents an interface that has a physical
       hardware representation, or is modelled as such.";
  }

  identity virtual {
    base iana-if-property-type;
    description
      "This property represents an interface that has no external
       physical hardware representation, and is used to represent
       interfaces that are created via configuration.";
  }

  identity sub-interface {
    base iana-if-property-type;
    description
      "This property represents an interface that is a child
       interface that is parented to another interface.";
  }

  identity point-to-point {
    base iana-if-property-type;
    description
      "This property represents an interface that is always
       point-to-point, i.e. the interface can only ever be connected
       to a single other interface, and hence broadcast and multicast
       packet statistics do not make sense.";
  }

  identity multicast {
    base iana-if-property-type;
    description
      "This property represents an interface that could have multiple
       end points, e.g. like an Ethernet interface.  Such an
       interface could have separate broadcast and multicast packet
       counters.";
  }

  identity ethernet-like {
    base iana-if-property-type;
    description
      "This property represents an interface that is similar in
       behaviour to an Ethernet interface, and uses Ethernet
       framing.";
  }
}
